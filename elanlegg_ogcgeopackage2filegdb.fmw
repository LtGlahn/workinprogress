FME workspace elanlegg_ogcgeopackage2filegdb.fmw

Parameters:
- DestDataset_FILEGDB =
- SourceDataset_OGCGEOPACKAGE_3 =

Readers:
- OGCGEOPACKAGE_2: OGCGEOPACKAGE from $(SourceDataset_OGCGEOPACKAGE_3)

Writers:
- FILEGDB_1: FILEGDB to $(DestDataset_FILEGDB)

GeometryFilter
    BREAK_AGG = Yes
    GEOM_PORT_NAMES = Point Line Arc Area Collection Null
    INSTANTIATE = Yes
    POINT -> lysarmatur (writer FILEGDB_1)

Bookmark: Reader Feature Types
lysarmatur (reader OGCGEOPACKAGE_2)
    attributes: objekttype int, nvdbId int, versjon int, startdato text, Geometri, punkt text, Antall armaturer i belysningspkt double, Lyskilde type text, Antall lyskilder per armatur double, ElAnlegg_Bruksområde text, ElAnlegg_nvdbId int, ElAnlegg_geom text, vegsystemreferanser text, stedfestinger text, geometri text, LED, Effekt armatur, totalt (test) double, Etableringsår double, Lysflux double, Fargetemperatur double, Fargegjengivelsesindeks double, Utstyrsklasse text, Konstant lysutbytte text, Eier text, Vedlikeholdsansvarlig text, Produktnavn, armatur text, Effekt double, Utgår_Type text, Dimming text, Optikk text, Inngår i nødsystemet text, Utskiftbare lyskilder text,
      Høyde over veg double, Avskjerming, materiale text, Avskjerming, type text, Produsent, armatur text, Tilleggsinformasjon text, Produsent, lyskilde text, Prosjektreferanse text, Eier, navn text, Leverandør text, Utgår_Utleggerarmens lengde double, Utgår_Lampeinnstilling text, Driftsmerking text, Lyskilde sist skiftet text, Produsent, driver text, LED, effekt per stk double, Armaturnummer text, Driftsstrøm, udimmet double, Utgår_Lengde double, Kommunikasjonsenhet text, LED, antall dioder double, Arkivreferanse text, vegkartlenke text
    -> GeometryFilter
kartvisning_lysarmatur (reader OGCGEOPACKAGE_2)
    attributes: objekttype int, nvdbId int, versjon int, startdato text, Geometri, punkt text, Antall armaturer i belysningspkt double, Lyskilde type text, Antall lyskilder per armatur double, ElAnlegg_Bruksområde text, ElAnlegg_nvdbId int, ElAnlegg_geom text, vegsystemreferanser text, stedfestinger text, geometri text, LED, Effekt armatur, totalt (test) double, Etableringsår double, Lysflux double, Fargetemperatur double, Fargegjengivelsesindeks double, Utstyrsklasse text, Konstant lysutbytte text, Eier text, Vedlikeholdsansvarlig text, Produktnavn, armatur text, Effekt double, Utgår_Type text, Dimming text, Optikk text, Inngår i nødsystemet text, Utskiftbare lyskilder text,
      Høyde over veg double, Avskjerming, materiale text, Avskjerming, type text, Produsent, armatur text, Tilleggsinformasjon text, Produsent, lyskilde text, Prosjektreferanse text, Eier, navn text, Leverandør text, Utgår_Utleggerarmens lengde double, Utgår_Lampeinnstilling text, Driftsmerking text, Lyskilde sist skiftet text, Produsent, driver text, LED, effekt per stk double, Armaturnummer text, Driftsstrøm, udimmet double, Utgår_Lengde double, Kommunikasjonsenhet text, LED, antall dioder double, Arkivreferanse text, vegkartlenke text
    -> kartvisning_lysarmatur (writer FILEGDB_1)
elanlegg_uten_lysarmatur (reader OGCGEOPACKAGE_2)
    attributes: objekttype int, nvdbId int, versjon int, startdato text, I tunnel text, Tunnelløp ID double, vegsystemreferanser text, stedfestinger text, geometri text, Nettselskap text, ElAnlegg_Bruksområde text, Geometri, punkt text, Antall NVDB-objekter lysarmatur double, Driftsmerking text, Vedlikeholdsansvarlig text, Eier text, Plassering, måler text, Merknad text, Bygget etter forskrift text, Bygget etter norm text, Fjernavlesing text, Nettsystem text, Inngår i nødsystemet text, Jordelektrode text, Måling type text, Spenning text, Jordfeilbryter text, Utgår_Kundenummer text, Utgår_Anleggsnummer text, Etableringsår double,
      Samlet effekt, lysarmatur double, Utgår_Avlesingsmetode text, Jordfeilvarsling text, Tilleggsinformasjon text, Utgår_Avstand fra vegkant double, Arkivreferanse text, Effekt double, Eier, navn text, Integrert med text, Prosjektreferanse text, Anleggsadresse text, Energikilde text, vegkartlenke text
    -> elanlegg_uten_lysarmatur (writer FILEGDB_1)
elanlegg_m_lysarmatur (reader OGCGEOPACKAGE_2)
    attributes: objekttype int, nvdbId int, versjon int, startdato text, I tunnel text, Tunnelløp ID double, vegsystemreferanser text, stedfestinger text, geometri text, Nettselskap text, ElAnlegg_Bruksområde text, Geometri, punkt text, Antall NVDB-objekter lysarmatur double, Driftsmerking text, Vedlikeholdsansvarlig text, Eier text, Plassering, måler text, Merknad text, Bygget etter forskrift text, Bygget etter norm text, Fjernavlesing text, Nettsystem text, Inngår i nødsystemet text, Jordelektrode text, Måling type text, Spenning text, Jordfeilbryter text, Utgår_Kundenummer text, Utgår_Anleggsnummer text, Etableringsår double,
      Samlet effekt, lysarmatur double, Utgår_Avlesingsmetode text, Jordfeilvarsling text, Tilleggsinformasjon text, Utgår_Avstand fra vegkant double, Arkivreferanse text, Effekt double, Eier, navn text, Integrert med text, Prosjektreferanse text, Anleggsadresse text, Energikilde text, vegkartlenke text
    -> elanlegg_m_lysarmatur (writer FILEGDB_1)

Bookmark: Writer Feature Types
lysarmatur (writer FILEGDB_1)
    attributes: objekttype int, nvdbId int, versjon int, startdato text(20), Dimming text(2048), Antall_armaturer_i_belysningspkt int, Optikk text(2048), Inngår_i_nødsystemet text(2048), Lyskilde_type text(2048), Utstyrsklasse text(2048), Utskiftbare_lyskilder text(2048), Eier text(2048), Antall_lyskilder_per_armatur text(20), Vedlikeholdsansvarlig text(2048), Effekt text(20), ElAnlegg_Bruksområde text(2048), ElAnlegg_nvdbId text(20), ElAnlegg_geom text(2048), vegsystemreferanser text(2048), stedfestinger text(2048), geometri text(2048), Høyde_over_veg text(20), Avskjerming__materiale text(2048), Avskjerming__type text(2048), Geometri__punkt text(2048), Produsent__armatur text(2048), Produktnavn__armatur text(2048), Utgår_Type text(2048), Etableringsår text(20), Produsent__lyskilde text(2048),
      LED__Effekt_armatur__totalt__test_ text(20), Eier__navn text(2048), Leverandør text(2048), Utgår_Utleggerarmens_lengde text(20), Utgår_Lampeinnstilling text(2048), Tilleggsinformasjon text(2048), Driftsmerking text(2048), Lysflux text(2048), Fargetemperatur text(2048), Prosjektreferanse text(2048), Lyskilde_sist_skiftet text(2048), Produsent__driver text(2048), Konstant_lysutbytte text(2048), LED__effekt_per_stk text(20), Armaturnummer text(2048), Driftsstrøm__udimmet text(20), Fargegjengivelsesindeks text(20), Utgår_Lengde text(20), Kommunikasjonsenhet text(2048), LED__antall_dioder text(20), Arkivreferanse text(2048), vegkartlenke text(2048)
kartvisning_lysarmatur (writer FILEGDB_1)
    attributes: objekttype text(20), nvdbId text(20), versjon text(20), startdato text(2048), Dimming text(2048), Antall_armaturer_i_belysningspkt double, Optikk text(2048), Inngår_i_nødsystemet text(2048), Lyskilde_type text(2048), Utstyrsklasse text(2048), Utskiftbare_lyskilder text(2048), Eier text(2048), Antall_lyskilder_per_armatur double, Vedlikeholdsansvarlig text(2048), Effekt double, ElAnlegg_Bruksområde text(2048), ElAnlegg_nvdbId text(20), ElAnlegg_geom text(2048), vegsystemreferanser text(2048), stedfestinger text(2048), geometri text(2048), Høyde_over_veg double, Avskjerming__materiale text(2048), Avskjerming__type text(2048), Geometri__punkt text(2048), Produsent__armatur text(2048), Produktnavn__armatur text(2048), Utgår_Type text(2048), Etableringsår double, Produsent__lyskilde text(2048),
      LED__Effekt_armatur__totalt__test_ double, Eier__navn text(2048), Leverandør text(2048), Utgår_Utleggerarmens_lengde double, Utgår_Lampeinnstilling text(2048), Tilleggsinformasjon text(2048), Driftsmerking text(2048), Lysflux double, Fargetemperatur double, Prosjektreferanse text(2048), Lyskilde_sist_skiftet text(2048), Produsent__driver text(2048), Konstant_lysutbytte text(2048), LED__effekt_per_stk double, Armaturnummer text(2048), Driftsstrøm__udimmet double, Fargegjengivelsesindeks double, Utgår_Lengde double, Kommunikasjonsenhet text(2048), LED__antall_dioder double, Arkivreferanse text(2048), vegkartlenke text(2048)
elanlegg_uten_lysarmatur (writer FILEGDB_1)
    attributes: objekttype int, nvdbId int, versjon int, startdato text(2048), I_tunnel text(2048), Tunnelløp_ID text(20), vegsystemreferanser text(2048), stedfestinger text(2048), geometri text(2048), Nettselskap text(2048), ElAnlegg_Bruksområde text(2048), Geometri__punkt text(2048), Antall_NVDB_objekter_lysarmatur int, Driftsmerking text(2048), Vedlikeholdsansvarlig text(2048), Eier text(2048), Plassering__måler text(2048), Merknad text(2048), Bygget_etter_forskrift text(2048), Bygget_etter_norm text(2048), Fjernavlesing text(2048), Nettsystem text(2048), Inngår_i_nødsystemet text(2048), Jordelektrode text(2048), Måling_type text(2048), Spenning text(2048), Jordfeilbryter text(2048), Utgår_Kundenummer text(2048), Utgår_Anleggsnummer text(2048), Etableringsår text(20),
      Samlet_effekt__lysarmatur text(20), Utgår_Avlesingsmetode text(2048), Jordfeilvarsling text(2048), Tilleggsinformasjon text(2048), Utgår_Avstand_fra_vegkant text(20), Arkivreferanse text(2048), Effekt text(20), Eier__navn text(2048), Integrert_med text(2048), Prosjektreferanse text(2048), Anleggsadresse text(2048), Energikilde text(2048), vegkartlenke text(2048)
elanlegg_m_lysarmatur (writer FILEGDB_1)
    attributes: objekttype text(20), nvdbId text(20), versjon text(20), startdato text(2048), I_tunnel text(2048), Tunnelløp_ID text(20), vegsystemreferanser text(2048), stedfestinger text(2048), geometri text(2048), Nettselskap text(2048), ElAnlegg_Bruksområde text(2048), Geometri__punkt text(2048), Antall_NVDB_objekter_lysarmatur int, Driftsmerking text(2048), Vedlikeholdsansvarlig text(2048), Eier text(2048), Plassering__måler text(2048), Merknad text(2048), Bygget_etter_forskrift text(2048), Bygget_etter_norm text(2048), Fjernavlesing text(2048), Nettsystem text(2048), Inngår_i_nødsystemet text(2048), Jordelektrode text(2048), Måling_type text(2048), Spenning text(2048), Jordfeilbryter text(2048), Utgår_Kundenummer text(2048), Utgår_Anleggsnummer text(2048), Etableringsår text(20),
      Samlet_effekt__lysarmatur double, Utgår_Avlesingsmetode text(2048), Jordfeilvarsling text(2048), Tilleggsinformasjon text(2048), Utgår_Avstand_fra_vegkant double, Arkivreferanse text(2048), Effekt text(20), Eier__navn text(2048), Integrert_med text(2048), Prosjektreferanse text(2048), Anleggsadresse text(2048), Energikilde text(2048), vegkartlenke text(2048)
