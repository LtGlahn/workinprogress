FME workspace stikkrenner-hoydesjekk.fmw

Parameters:
- SourceDataset_GEOTIFF = C:\DATA\kartverket\DTEM\dtm50\data\*.tif   # Source GeoTIFF File(s)
- DestDataset_OGCGEOPACKAGE = $(FME_MF_DIR)hoydekontroll_DoVvest.gpkg   # GeoPackage File
- SourceDataset_OGCGEOPACKAGE_2 = $(FME_MF_DIR)stikkrenneDoVvest.gpkg   # GeoPackage File

Readers:
- GEOTIFF_1: GEOTIFF from $(SourceDataset_GEOTIFF)
- OGCGEOPACKAGE_3: OGCGEOPACKAGE from $(SourceDataset_OGCGEOPACKAGE_2)

Writers:
- OGCGEOPACKAGE_2: OGCGEOPACKAGE to $(DestDataset_OGCGEOPACKAGE)

type83_kum (reader OGCGEOPACKAGE_3)
    attributes: objekttype int, nvdbId int, versjon int, startdato text, Materialtype text, Lokk/rist, type text, Dybde double, Bruksområde text, Type text, Diameter double, relasjoner text, vegsystemreferanser text, stedfestinger text, Bredde1, firkantkum double, Bredde2, firkantkum double, Vedlikeholdsansvarlig text, Eier text, Geometri, punkt text, Avstand fra vegkant double, Etableringsår double, Inngår i drenssystem text, Spesiell belegning rundt kum text, Stige text, Plassering text, Prosjektreferanse text, Kumskjerm text, Produktnavn text, Stengeventil text, Oljeutskilling text, Dykker text,
      Har flyteramme text, Avløp text, Valideringsdato (test) text, Antall rør inn double, Diameter, åpning double, Tilleggsinformasjon text, Antall hjelpesluker double, Dybde til utløp double, Eier, navn text, Arkivreferanse text, FKB_ID text, Driftsmerking text, Leverandør text, Produsent text, Oppslammingstid text, ProsjektInternObjekt_ID text, fid int,PrimaryKey
    -> Tester_4
Tester_4
    BOOL_OP = OR
    TEST_CLAUSE = TEST Geometri, punkt ATTRIBUTE_HAS_A_VALUE ""
    TEST_MODE = TEST
    PASSED -> DimensionExtractor_2
DimensionExtractor_2
    DIM_ATTR = _dimension
    -> Tester_3
Tester_3
    BOOL_OP = OR
    TEST_CLAUSE = TEST @Value(_dimension) = 2
    TEST_MODE = TEST
    PASSED -> kum-2Degengeometri (writer OGCGEOPACKAGE_2)
    FAILED -> CoordinateExtractor_3
CoordinateExtractor_3
    LIST_NAME = _indices
    MODE = All Coordinates
    -> ListRangeExtractor_3
ListRangeExtractor_3
    MAX = _max_Z
    MIN = _min_Z
    SRC_LIST = _indices{}.z
    -> ExpressionEvaluator_4
ExpressionEvaluator_4
    ACTION = Create New Attribute
    EXPRESSION = @Value(_max_Z)-@Value(_min_Z)
    VAL_ATTR = maks_hoydeforskjell_egengeom
    -> SurfaceDraper_2 [DRAPE_FEATURES]
kum-2Degengeometri (writer OGCGEOPACKAGE_2)
    attributes: objekttype int, nvdbId int, versjon int, startdato text, Materialtype text, Lokk/rist, type text, Dybde double, Bruksområde text, Type text, Diameter double, relasjoner text, vegsystemreferanser text, stedfestinger text, Bredde1, firkantkum double, Bredde2, firkantkum double, Vedlikeholdsansvarlig text, Eier text, Geometri, punkt text, Avstand fra vegkant double, Etableringsår double, Inngår i drenssystem text, Spesiell belegning rundt kum text, Stige text, Plassering text, Prosjektreferanse text, Kumskjerm text, Produktnavn text, Stengeventil text, Oljeutskilling text, Dykker text,
      Har flyteramme text, Avløp text, Valideringsdato (test) text, Antall rør inn double, Diameter, åpning double, Tilleggsinformasjon text, Antall hjelpesluker double, Dybde til utløp double, Eier, navn text, Arkivreferanse text, FKB_ID text, Driftsmerking text, Leverandør text, Produsent text, Oppslammingstid text, ProsjektInternObjekt_ID text, fid int,PrimaryKey, _dimension double
type79_stikkrenne_kulvert (reader OGCGEOPACKAGE_3)
    attributes: objekttype int, nvdbId int, versjon int, startdato text, Har innløpsrist text, Bruksområde text, Materialtype text, Tverrsnittsform text, Type innløp text, Type utløp text, Tilknyttet lukka dren text, Diameter, innvendig double, Lengde double, relasjoner text, vegsystemreferanser text, stedfestinger text, Bredde, innvendig double, Høyde, innvendig double, Geometri, linje text, Etableringsår double, Overfylling innløp double, Prosjektreferanse text, Tykkelse overfylling double, Vinkel text, Retning double, Belegning innløp text, Belegning utløp text, Varmekabler text, Gjennomløp for elv/bekk text, Geometri, punkt text,
      Spesielle hensyn fiskevandring text, Eier text, Vedlikeholdsansvarlig text, Belegning stikkrenne text, Antall tininger double, Tilleggsinformasjon text, Arkivreferanse text, FKB_ID text, Arkivnummer text, Driftsmerking text, Navn text, Produktnavn, rør text, Prefabrikkert text, Fundamentering text, Helning/Fall double, Spesielle problem text, Høyde, passasje double, Geometri, flate text, Rehabilitering text, Overfylling utløp double, ProsjektInternObjekt_ID text, fid int,PrimaryKey
    -> Tester_2
Tester_2
    BOOL_OP = OR
    TEST_CLAUSE = TEST Geometri, linje ATTRIBUTE_HAS_A_VALUE ""
    TEST_MODE = TEST
    PASSED -> DimensionExtractor
DimensionExtractor
    DIM_ATTR = _dimension
    -> Tester
Tester
    BOOL_OP = OR
    TEST_CLAUSE = TEST @Value(_dimension) = 2
    TEST_MODE = TEST
    PASSED -> stikkrenner-2Degengeometri (writer OGCGEOPACKAGE_2)
    PASSED -> Kun2D
    FAILED -> CoordinateExtractor
stikkrenner-2Degengeometri (writer OGCGEOPACKAGE_2)
    attributes: objekttype int, nvdbId int, versjon int, startdato text, Har innløpsrist text, Bruksområde text, Materialtype text, Tverrsnittsform text, Type innløp text, Type utløp text, Tilknyttet lukka dren text, Diameter, innvendig double, Lengde double, relasjoner text, vegsystemreferanser text, stedfestinger text, Bredde, innvendig double, Høyde, innvendig double, Geometri, linje text, Etableringsår double, Overfylling innløp double, Prosjektreferanse text, Tykkelse overfylling double, Vinkel text, Retning double, Belegning innløp text, Belegning utløp text, Varmekabler text, Gjennomløp for elv/bekk text, Geometri, punkt text,
      Spesielle hensyn fiskevandring text, Eier text, Vedlikeholdsansvarlig text, Belegning stikkrenne text, Antall tininger double, Tilleggsinformasjon text, Arkivreferanse text, FKB_ID text, Arkivnummer text, Driftsmerking text, Navn text, Produktnavn, rør text, Prefabrikkert text, Fundamentering text, Helning/Fall double, Spesielle problem text, Høyde, passasje double, Geometri, flate text, Rehabilitering text, Overfylling utløp double, ProsjektInternObjekt_ID text, fid int,PrimaryKey, _dimension double
Kun2D: Inspector
CoordinateExtractor
    LIST_NAME = _indices
    MODE = All Coordinates
    -> ListRangeExtractor
ListRangeExtractor
    MAX = _max_Z
    MIN = _min_Z
    SRC_LIST = _indices{}.z
    -> ExpressionEvaluator
ExpressionEvaluator
    ACTION = Create New Attribute
    EXPRESSION = @Value(_max_Z)-@Value(_min_Z)
    VAL_ATTR = maks_hoydeforskjell_egengeom
    -> SurfaceDraper [DRAPE_FEATURES]
CoordinateExtractor_2
    LIST_NAME = _indices_DTM
    MODE = All Coordinates
    -> ListRangeExtractor_2
ListRangeExtractor_2
    MAX = _max_Z_DTM
    MIN = _min_Z_DTM
    SRC_LIST = _indices_DTM{}.z
    -> ExpressionEvaluator_2
ExpressionEvaluator_2
    ACTION = Create New Attribute
    EXPRESSION = @Value(_max_Z_DTM)-@Value(_min_Z_DTM)
    VAL_ATTR = maks_hoydeforskjell_DTM
    -> ExpressionEvaluator_3
ExpressionEvaluator_3
    ACTION = Create New Attribute
    EXPRESSION = @max( @abs(  @Value(_max_Z)-@Value(_max_Z_DTM) ), @abs(  @Value(_min_Z)-@Value(_min_Z_DTM) ))
    VAL_ATTR = hoydediff_egen_DTM
    -> AttributeRemover
AttributeRemover
    LIST_ATTRS = _indices_DTM{} _indices_DTM{}.x _indices_DTM{}.y _indices_DTM{}.z _indices{} _indices{}.x _indices{}.y _indices{}.z
    REMOVE_ATTRS = _dimension
    -> stikkrenner_kontroll
    -> stikkrenner-kontroll (writer OGCGEOPACKAGE_2)
stikkrenner-kontroll (writer OGCGEOPACKAGE_2)
    attributes: objekttype int, nvdbId int, versjon int, startdato text, Har innløpsrist text, Bruksområde text, Materialtype text, Tverrsnittsform text, Type innløp text, Type utløp text, Tilknyttet lukka dren text, Diameter, innvendig double, Lengde double, relasjoner text, vegsystemreferanser text, stedfestinger text, Bredde, innvendig double, Høyde, innvendig double, Geometri, linje text, Etableringsår double, Overfylling innløp double, Prosjektreferanse text, Tykkelse overfylling double, Vinkel text, Retning double, Belegning innløp text, Belegning utløp text, Varmekabler text, Gjennomløp for elv/bekk text, Geometri, punkt text,
      Spesielle hensyn fiskevandring text, Eier text, Vedlikeholdsansvarlig text, Belegning stikkrenne text, Antall tininger double, Tilleggsinformasjon text, Arkivreferanse text, FKB_ID text, Arkivnummer text, Driftsmerking text, Navn text, Produktnavn, rør text, Prefabrikkert text, Fundamentering text, Helning/Fall double, Spesielle problem text, Høyde, passasje double, Geometri, flate text, Rehabilitering text, Overfylling utløp double, ProsjektInternObjekt_ID text, fid int,PrimaryKey, _min_Z double, _max_Z double, maks_hoydeforskjell_egengeom double, _min_Z_DTM double, _max_Z_DTM double, maks_hoydeforskjell_DTM double, hoydediff_egen_DTM double
stikkrenner_kontroll: Inspector
CoordinateExtractor_4
    LIST_NAME = _indices_DTM
    MODE = All Coordinates
    -> ListRangeExtractor_4
ListRangeExtractor_4
    MAX = _max_Z_DTM
    MIN = _min_Z_DTM
    SRC_LIST = _indices_DTM{}.z
    -> ExpressionEvaluator_5
ExpressionEvaluator_5
    ACTION = Create New Attribute
    EXPRESSION = @Value(_max_Z_DTM)-@Value(_min_Z_DTM)
    VAL_ATTR = maks_hoydeforskjell_DTM
    -> ExpressionEvaluator_6
ExpressionEvaluator_6
    ACTION = Create New Attribute
    EXPRESSION = @max( @abs(  @Value(_max_Z)-@Value(_max_Z_DTM) ), @abs(  @Value(_min_Z)-@Value(_min_Z_DTM) ))
    VAL_ATTR = hoydediff_egen_DTM
    -> AttributeRemover_2
AttributeRemover_2
    LIST_ATTRS = _indices_DTM{} _indices_DTM{}.x _indices_DTM{}.y _indices_DTM{}.z _indices{} _indices{}.x _indices{}.y _indices{}.z
    REMOVE_ATTRS = _dimension
    -> kum-kontroll (writer OGCGEOPACKAGE_2)
    -> AttributeRemover_2_Output
kum-kontroll (writer OGCGEOPACKAGE_2)
    attributes: objekttype int, nvdbId int, versjon int, startdato text, Materialtype text, Lokk/rist, type text, Dybde double, Bruksområde text, Type text, Diameter double, relasjoner text, vegsystemreferanser text, stedfestinger text, Bredde1, firkantkum double, Bredde2, firkantkum double, Vedlikeholdsansvarlig text, Eier text, Geometri, punkt text, Avstand fra vegkant double, Etableringsår double, Inngår i drenssystem text, Spesiell belegning rundt kum text, Stige text, Plassering text, Prosjektreferanse text, Kumskjerm text, Produktnavn text, Stengeventil text, Oljeutskilling text, Dykker text,
      Har flyteramme text, Avløp text, Valideringsdato (test) text, Antall rør inn double, Diameter, åpning double, Tilleggsinformasjon text, Antall hjelpesluker double, Dybde til utløp double, Eier, navn text, Arkivreferanse text, FKB_ID text, Driftsmerking text, Leverandør text, Produsent text, Oppslammingstid text, ProsjektInternObjekt_ID text, fid int,PrimaryKey, _min_Z double, _max_Z double, maks_hoydeforskjell_egengeom double, _min_Z_DTM double, _max_Z_DTM double, maks_hoydeforskjell_DTM double, hoydediff_egen_DTM double
AttributeRemover_2_Output: Inspector

Bookmark: New Bookmark
GEOTIFF (reader GEOTIFF_1)
    attributes: datatype char(255)
    -> SurfaceDraper [POINTS/LINES]
    -> SurfaceDraper_2 [POINTS/LINES]
SurfaceDraper
    ADDZ_TYPE = Replace Z
    DRAPE_TYPE = VERTEX
    INTERPOLATION_TYPE = AUTO
    TOLERANCE = 1
    DRAPED_FEATURES -> CoordinateExtractor_2
SurfaceDraper_2
    ADDZ_TYPE = Replace Z
    DRAPE_TYPE = VERTEX
    INTERPOLATION_TYPE = AUTO
    TOLERANCE = 1
    DRAPED_FEATURES -> CoordinateExtractor_4
